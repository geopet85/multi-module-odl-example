module negotiator {
    yang-version 1;
    namespace "urn:eu:virtuwind:negotiator";
    prefix negotiator;

    import opendaylight-inventory {prefix inv; revision-date 2013-08-19;}
    import yang-ext {prefix ext; revision-date "2013-07-09";}
    import ietf-yang-types { prefix yang; revision-date 2010-09-24; }
    import ietf-inet-types { prefix inet; }
    description "QoS negotiator configuration";

    revision "2015-07-22" {
        description "Initial version.";
    }

    typedef NegotiationOutcome {
                type enumeration {
                    enum "ACCEPT";
                    enum "REJECT";
                    enum "NEGOTIATE";
                }
            }

        rpc negotiation {
                    input {
                        leaf appId {
                            type int32;
                        }
                        leaf bandwidth {
                            type decimal64{
                                fraction-digits 4;
                            }
                        }
                        leaf packetLoss {
                            type decimal64{
                                fraction-digits 4;
                            }
                        }
                        leaf packetDelay {
                            type decimal64{
                                fraction-digits 4;
                            }
                        }
                        leaf jitter {
                            type decimal64{
                                fraction-digits 4;
                            }
                        }
                    }
                    output {
                        leaf appId {
                            type int32;
                        }
                        leaf response {
                            type NegotiationOutcome;
                        }
                        leaf diffBandwidth {
                            type decimal64{
                                fraction-digits 4;
                            }
                        }
                        leaf diffPacketLoss {
                            type decimal64{
                                fraction-digits 4;
                            }
                        }
                        leaf diffPacketDelay {
                            type decimal64{
                                fraction-digits 4;
                            }
                        }
                        leaf diffJitter {
                            type decimal64{
                                fraction-digits 4;
                            }
                        }
                    }

                }


}
